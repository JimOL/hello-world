FME workspace GeoJson.fmw

Parameters:
- SourceDataset_SDF3 = C:\FMEData\Data\Transit\Transit.sdf   # Source Autodesk MapGuide Enterprise SDF File(s)
- DestDataset_TEXTLINE_3 = D:\projects\other\geojson_streaming_demo\output\out.txt   # Destination Text File

Readers:
- SDF3_1: SDF3 from $(SourceDataset_SDF3) in TX83-CF

Writers:
- TEXTLINE_1: TEXTLINE to $(DestDataset_TEXTLINE_3)

Default.BusRoutes (reader SDF3_1)
    attributes: LINE_ID char(5), LINE_NAME char(50), PRIMARYINDEX int32
    -> Reprojector
Reprojector
    INTERPOLATION_TYPE_NAME = Nearest Neighbor
    RASTER_CELL_SIZE = Preserve Cells
    SOURCE = TX83-CF
    DEST = LL83
    REPROJECTED -> GeometryExtractor
GeometryExtractor
    ATTR = _geometry
    KIND_LONG = GeoJSON
    -> JSONTemplater_1
Note: FME Server does not / stream this output
text_line (writer TEXTLINE_1)
    attributes: text_line_data buffer

Bookmark: Make the JSON output
JSONTemplater_1
    ROOT_QUERY_EXPR = {'type':'Feature',"geometry":{fme:get-attribute("_geometry")},"properties":{"LINE_ID":fme:get-attribute("LINE_ID"),"LINE_NAME":fme:get-attribute("LINE_NAME"),"PRIMARYINDEX":fme:get-attribute("PRIMARYINDEX")}}
    RESULT_ATTRIBUTE = jsonRoute
    VISIBLE_QUERY_VALIDATE = Yes
    -> PythonCaller
PythonCaller
    PYTHONSOURCE:
      import fme
      import fmeobjects
      import string

      # Template Class Interface:
      class FeatureProcessor(object):
          def __init__(self):
              self.lstFeature = []
          def input(self,feature):
              jsonRoute = feature.getAttribute("jsonRoute")
              jsonRoute = string.replace(jsonRoute,"\\","")
              jsonRoute = string.replace(jsonRoute,'"{"','{"')
              jsonRoute = string.replace(jsonRoute,'}",','},')
              jsonRoute = string.replace(jsonRoute," ","")
              self.lstFeature.append(jsonRoute)
              self.aFeature =feature # keep a feature for the close pyoutput


          def close(self):
              strAllFeature = string.join(self.lstFeature,"\n,")
              text_line_data = \
              '''{"name":"Default.BusRoutes","type":"FeatureCollection"
      ,"features":[
      %s]}''' % strAllFeature
              self.aFeature.setAttribute("text_line_data",text_line_data)
              self.pyoutput(self.aFeature)
    PYTHONSYMBOL = FeatureProcessor
    NEW_ATTRIBUTES = text_line_data
    -> text_line (writer TEXTLINE_1)
